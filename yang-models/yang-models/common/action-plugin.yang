module local-action-plugin {
    namespace "http://github.com/sonic-net/sonic-action-binding";
    prefix evtbnd;
    yang-version 1.1;

    import ietf-yang-types {
        prefix yang;
    }

    organization
        "SONiC";

    contact
        "SONiC";

    description
        "action binding definition";

    revision 2022-12-01 {
        description
            "Binding schema";
    } 

    container LOCAL-ACTION-PLUGIN {
        description "Plugin mapped to corresponding action";
        
        list bindings-list {

            key "ACTION-NAME";

            leaf ACTION-NAME {
                type string;
                description "Fully qualified ame of the action as
                    <yang module name>:<container name>";
            }
            leaf plugin-path {
                type string
                description "Plugin binary location";
            }
            leaf-list args {
                type string
                description "List of args passed as args to plugin at startup";
            }
        } 
    }
}
